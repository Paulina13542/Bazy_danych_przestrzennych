FME workspace cw_12.fmw

Parameters:
- SourceDataset_SHAPEFILE = $(FME_MF_DIR)T2019_KAR_GERMANY\T2019_KAR_POI_TABLE.shp   # Source Esri Shapefile(s)
- SourceDataset_SHAPEFILE_5 = $(FME_MF_DIR)T2019_KAR_GERMANY\T2019_KAR_STREET_NODE.shp   # Source Esri Shapefile(s)
- SourceDataset_SHAPEFILE_4 = $(FME_MF_DIR)T2019_KAR_GERMANY\T2019_KAR_STREETS.shp   # Source Esri Shapefile(s)
- SourceDataset_CSV2 = $(FME_MF_DIR)trasa.csv   # Source CSV (Comma Separated Value) File(s)

Readers:
- SHAPEFILE_1: SHAPEFILE from $(SourceDataset_SHAPEFILE)
- SHAPEFILE_2: SHAPEFILE from $(SourceDataset_SHAPEFILE_5)
- SHAPEFILE_3: SHAPEFILE from $(SourceDataset_SHAPEFILE_4)
- CSV2_1: CSV2 from $(SourceDataset_CSV2)

T2019_KAR_STREET_NODE (reader SHAPEFILE_2)
    attributes: NODE_ID long, LINK_ID long, POINT_NUM long, Z_LEVEL long, INTERSECT varchar(1), LAT number(31,15), LON number(31,15)
    -> Reprojector
T2019_KAR_STREETS (reader SHAPEFILE_3)
    attributes: LINK_ID long, ST_NAME varchar(254), REF_IN_ID long, NREF_IN_ID long, FUNC_CLASS varchar(1), SPEED_CAT varchar(1), FR_SPEED_L long, TO_SPEED_L long, DIR_TRAVEL varchar(1)
    -> Reprojector
CSV (reader CSV2_1)
    attributes: x real32, y real32
    -> VertexCreator
VertexCreator
    MEASURE_TYPE_LOOKUP = CONTINUOUS
    MODE = REPLACE
    REMOVE_ATTRIBUTES = No
    XVAL = @Value(x)
    YVAL = @Value(y)
    MEASURE_TYPE = Continuous
    MODE_NAME = Replace with Point
    -> LineBuilder
LineBuilder
    ACCUM_INPUT_ATTRS_LOOKUP = One
    REMOVE_DUPLICATES_LOOKUP = NO
    ACCUM_INPUT_ATTRS = Use Attributes From One Feature
    REMOVE_DUPLICATES = No
    LINE -> Reprojector_2
Reprojector_2
    DEST = DHDN.Berlin/Cassini
    INTERPOLATION_TYPE = NearestNeighbor
    RASTER_CELL_SIZE = PreserveCells
    RASTER_TOLERANCE = 0.0
    SOURCE = EPSG:4326
    REPROJECTED -> ShortestPathFinder [FROM-TO]
    REPROJECTED -> ShortestPathFinder_2 [FROM-TO]
T2019_KAR_POI_TABLE (reader SHAPEFILE_1)
    attributes: POI_ID long, LINK_ID long, TYPE varchar(250), POI_NAME varchar(250), ST_NAME varchar(250), LAT number(31,15), LON number(31,15)
    -> Reprojector
Reprojector
    DEST = DHDN.Berlin/Cassini
    INTERPOLATION_TYPE = NearestNeighbor
    RASTER_CELL_SIZE = PreserveCells
    RASTER_TOLERANCE = 0.0
    SOURCE = EPSG:4326
    REPROJECTED -> TestFilter
TestFilter
    DEFAULT_VALUE = <UNFILTERED>
    PASSED_TEST_GROUP_OUTPUT = FIRST
    TEST_LIST = "BOOL_OP,OR,COMPOSITE_TEST,""""""1"""""",TEST_CLAUSE,TEST @Value(fme_feature_type) = T2019_KAR_STREETS",STREETS,"BOOL_OP,OR,COMPOSITE_TEST,""""""1"""""",TEST_CLAUSE,TEST @Value(fme_feature_type) = T2019_KAR_POI_TABLE",POI,"BOOL_OP,OR,COMPOSITE_TEST,""""""1"""""",TEST_CLAUSE,TEST @Value(fme_feature_type) = T2019_KAR_STREET_NODE",NODES
    STREETS -> ShortestPathFinder [NETWORK]
    STREETS -> Tester
    POI -> SpatialFilter [Candidate]
    NODES -> SpatialFilter_2 [Candidate]
Tester
    BOOL_OP = OR
    TEST_CLAUSE = TEST @Value(DIR_TRAVEL) = B
    TEST_MODE = TEST
    PASSED -> AttributeCreator_2
    FAILED -> AttributeCreator_3
AttributeCreator_2
    ATTR_TABLE = SET_TO _koszt (uint8) = 1
    INPUT_PORT_CONNECTED = CONNECTED
    -> ShortestPathFinder_2 [NETWORK]
AttributeCreator_3
    ATTR_TABLE = SET_TO _koszt (uint8) = 5
    INPUT_PORT_CONNECTED = CONNECTED
    -> ShortestPathFinder_2 [NETWORK]
ShortestPathFinder_2
    ALLOW_UTURNS = Yes
    REORDER_MODE = NONE
    SNAP_POINTS = Yes
    SNAP_TOLERANCE = 200
    THREE_D = No
    WEIGHT_ATTR_1 = @Value(_koszt)
    WEIGHT_ATTR_2 = @Value(_koszt)
    WEIGHT_ATTR_CHOICE = BY_TWO_ATTRIBUTES
    PATH -> AttributeCreator_4
AttributeCreator_4
    ATTR_TABLE = SET_TO Wariant (varchar(10)) = Z_Kosztami
    INPUT_PORT_CONNECTED = CONNECTED
    -> Bufferer
    -> _length
ShortestPathFinder
    ALLOW_UTURNS = Yes
    REORDER_MODE = NONE
    SNAP_POINTS = Yes
    SNAP_TOLERANCE = 200
    THREE_D = No
    WEIGHT_ATTR_CHOICE = BY_LENGTH
    PATH -> AttributeCreator
AttributeCreator
    ATTR_TABLE = SET_TO Wariant (varchar(11)) = Bez_Kosztow
    INPUT_PORT_CONNECTED = CONNECTED
    -> Bufferer
    -> _length
Bufferer
    ANGLE = 22.5
    CAP_STYLE_LOOKUP = CAP_ARC
    CORNER_STYLE_LOOKUP = JOIN_ARC
    MODE = AREA
    OFFSET = 5
    OFFSET_UNITS = METERS
    PRECISION = APPROX
    CAP_STYLE = Arc
    CORNER_STYLE = Arc
    BUFFERED -> SpatialFilter [Filter]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> FeatureWriter [NewFeatureType]
_length: LengthCalculator
    DIM = 2
    LEN_ATTR = _length
    MULT = 1
    -> SpatialFilter_2 [Filter]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> StatisticsCalculator
StatisticsCalculator
    ATTR_ACCUM_MODE = None
    CALCULATION_MODE = NUMERIC
    FEAT_STATS = _length,NUMERIC_MODE,,,COUNT,,MEAN,,,,,,,,
    GROUP_BY = Wariant
    SUMMARY -> FeatureWriter [NewFeatureType]
FeatureWriter
    CONFIG_PARAMETERS = ESCAPE_COMMAS_IN_FTP_FORMAT_PARAMETERS,no
    DATASET = C:\Users\pauli\Bazy_danych
    DATASET_ATTR = _dataset
    FEATURE_TYPE_LIST_ATTR = _feature_types
    FORMAT = JSON
    JSON_COORDINATE_SYSTEM_FORMAT = OGC-WKT
    JSON_COORDINATE_SYSTEM_KEY = json_ogc_wkt_crs
    JSON_DESTINATION_DATASETTYPE_VALIDATION = Yes
    JSON_FEATURE_TYPE_KEY = json_featuretype
    JSON_GEOMETRY_FORMAT = GeoJSON
    JSON_GEOMETRY_KEY = json_geometry
    JSON_INDENT_SIZE = 0
    JSON_MAX_COORDINATE_PRECISION = 10
    JSON_PRETTY_PRINT = YES
    JSON_WRITER_CHARSET = UTF-8
    JSON_WRITE_BOM = No
    JSON_WRITE_COORDINATE_SYSTEM = YES
    JSON_WRITE_FEATURE_TYPE_KEY = YES
    JSON_WRITE_GEOMETRY = YES
    JSON_WRITE_NESTED = YES
    TOTAL_FEATURES_WRITTEN_ATTR = _total_features_written
